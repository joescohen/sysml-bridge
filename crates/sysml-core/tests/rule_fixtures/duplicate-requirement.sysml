package F {
    requirement <'R-1'> range { doc /* The vehicle shall travel 300 km on one charge. */ }
    package Copy { requirement <'R-2'> rangeAgain { doc /* The vehicle shall travel 300 km on one charge. */ } }
}
